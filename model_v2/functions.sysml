package TandemFunctions {
    private import Tandem::*;
    private import ScalarValues::Boolean;

    action def HoldPosition {
        doc /* Keep drone at its curerent position and height. */
    }
}
